module net-device {
    namespace uri:example:net-device;
    prefix dev;

    typedef ipv4-address {
        type string {
            pattern '^((25[0-5]|2[0-4][0-9]|1[0-9][0-9]|[1-9]?[0-9])\.){3}(25[0-5]|2[0-4][0-9]|1[0-9][0-9]|[1-9]?[0-9])$';
        }
    }

    container device {
        leaf hostname {
            type string;
        }
        leaf mgmt-ip {
            type ipv4-address;
        }
        container spanning-tree {
            container mst {
                leaf region-name {
                    type string;
                }
            }
        }
        
        list non-keyed-list {
            config false;
            container foobar {
                leaf sub-item {
                    type string;
                }
            }
            leaf test-item {
                type string;
            }
        }
        
        container interfaces {
            list interface {
                key name;
                leaf name {
                    type string;
                }
                leaf enabled {
                    type boolean;
                }
            }
        }
        leaf-list dns-server {
            type string;
        }
    }
}
